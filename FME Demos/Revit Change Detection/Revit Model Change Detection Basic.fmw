FME workspace Revit Model Change Detection Basic.fmw
Title: Revit Change Detection Basic

Parameters:
- SourceDataset_REVITNATIVE =
- SourceDataset_REVITNATIVE_3 =

Readers:
- REVITNATIVE_1: REVITNATIVE from $(SourceDataset_REVITNATIVE)
- REVITNATIVE_2: REVITNATIVE from $(SourceDataset_REVITNATIVE_3)

ChangeDetector
    BLANK_AND_MISSING_DIFFER = No
    BLANK_AND_MISSING_NAMES_TRAITS_DIFFER = No
    CHECK_COORDINATE_SYSTEMS = No
    CHECK_TYPES_AND_ENCODINGS = No
    LENIENT_MATCH = Yes
    MATCH = FULL
    MATCHATTRS = UniqueId
    MATCH_STRATEGY = Match Selected Attributes
    UNCHANGED_OUTPUT = Output Original
    UPDATED -> GeometryColorSetter_2
    INSERTED -> GeometryColorSetter
    DELETED -> GeometryColorSetter_3
    UNCHANGED -> GeometryColorSetter_4

Bookmark: Old Revit Files
Architectural.CurtainWallMullions (reader REVITNATIVE_2)
    attributes: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
Architectural.Columns (reader REVITNATIVE_2)
    attributes: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
Architectural.CurtainPanels (reader REVITNATIVE_2)
    attributes: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
Architectural.Doors (reader REVITNATIVE_2)
    attributes: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
Architectural.Floors (reader REVITNATIVE_2)
    attributes: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
Architectural.Rooms (reader REVITNATIVE_2)
    attributes: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
Architectural.Walls (reader REVITNATIVE_2)
    attributes: ObjectId number(10,0), BuildingLevelElevation number(31,15), BuildingLevelRoomOffset number(31,15), BuildingLevelIsStory char(3), BaseCategory char(5), BuildingLevel char(24), Category char(5), Constraints.BaseExtensionDistance number(31,15), Constraints.BaseOffset number(31,15), Constraints.TopExtensionDistance number(31,15), Constraints.TopOffset number(31,15), Constraints.UnconnectedHeight number(31,15), CreatedPhase char(16), Discipline char(13), ElementType char(5), Family char(10), FamilyType char(21), Function char(8), InExteriorShell char(3), Other.WALL_BASE_OFFSET_COMPUTED number(31,15), Other.WALL_FAKE_END_PARAM_0 number(31,15), Other.WALL_FAKE_END_PARAM_1 number(31,15), Other.WALL_HEIGHT_PARAM number(31,15), UniqueId char(45), WorksetName char(8)
    -> ChangeDetector [ORIGINAL]

Bookmark: New Revit Files
Architectural.CurtainWallMullions (reader REVITNATIVE_1)
    attributes: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
Architectural.Columns (reader REVITNATIVE_1)
    attributes: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
Architectural.CurtainPanels (reader REVITNATIVE_1)
    attributes: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
Architectural.Doors (reader REVITNATIVE_1)
    attributes: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
Architectural.Floors (reader REVITNATIVE_1)
    attributes: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
Architectural.Rooms (reader REVITNATIVE_1)
    attributes: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
Architectural.Walls (reader REVITNATIVE_1)
    attributes: ObjectId number(10,0), BuildingLevelElevation number(31,15), BuildingLevelRoomOffset number(31,15), BuildingLevelIsStory char(3), BaseCategory char(5), BuildingLevel char(24), Category char(5), Constraints.BaseExtensionDistance number(31,15), Constraints.BaseOffset number(31,15), Constraints.TopExtensionDistance number(31,15), Constraints.TopOffset number(31,15), Constraints.UnconnectedHeight number(31,15), CreatedPhase char(16), Discipline char(13), ElementType char(5), Family char(10), FamilyType char(21), Function char(8), InExteriorShell char(3), Other.WALL_BASE_OFFSET_COMPUTED number(31,15), Other.WALL_FAKE_END_PARAM_0 number(31,15), Other.WALL_FAKE_END_PARAM_1 number(31,15), Other.WALL_HEIGHT_PARAM number(31,15), UniqueId char(45), WorksetName char(8)
    -> ChangeDetector [REVISED]

Bookmark: Set Colors
GeometryColorSetter_2
    ALPHA = 1
    FILL_COLOR = 0,0.333333,1
    MODE = Fixed
    REC = Yes
    SIDE = Both
GeometryColorSetter
    ALPHA = 1
    FILL_COLOR = 0,1,0
    MODE = Fixed
    REC = Yes
    SIDE = Both
GeometryColorSetter_3
    ALPHA = 1
    FILL_COLOR = 1,0,0
    MODE = Fixed
    REC = Yes
    SIDE = Both
GeometryColorSetter_4
    ALPHA = .25
    FILL_COLOR = 0.462745,0.462745,0.462745
    MODE = Fixed
    REC = Yes
    SIDE = Both
