FME workspace Revit to Excel Simple.fmw
Title: Revit to Excel Simple

Parameters:
- DestDataset_XLSXW =
- SourceDataset_REVITNATIVE =

Readers:
- REVITNATIVE_1: REVITNATIVE from $(SourceDataset_REVITNATIVE)

Writers:
- XLSXW_1: XLSXW to $(DestDataset_XLSXW)

Architectural.CurtainWallMullions (reader REVITNATIVE_1)
    attributes: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
Architectural.CurtainPanels (reader REVITNATIVE_1)
    attributes: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
Metadata.FileInformation (reader REVITNATIVE_1)
    attributes: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
Metadata.ViewInformation (reader REVITNATIVE_1)
    attributes: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
Architectural.Columns (reader REVITNATIVE_1)
    attributes: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
Architectural.Doors (reader REVITNATIVE_1)
    attributes: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
Architectural.Floors (reader REVITNATIVE_1)
    attributes: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
Architectural.Lines (reader REVITNATIVE_1)
    attributes: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
Architectural.Rooms (reader REVITNATIVE_1)
    attributes: ObjectId number(10,0), BuildingLevelElevation number(31,15), BuildingLevelRoomOffset number(31,15), BuildingLevelIsStory char(3), Dimensions.RoomArea number(31,15), BaseCategory char(5), BuildingLevel char(24), Category char(5), Discipline char(13), ElementType char(8), Family char(0), FamilyType char(0), IdentityData.RoomName char(7), IdentityData.RoomNumber char(2), InExteriorShell char(3), RoomSchedule.Area number(31,15), UniqueId char(45), WorksetName char(8)
    -> GeometryColorSetter
    -> Architectural.Rooms (writer XLSXW_1)
Architectural.Rooms (writer XLSXW_1)
    attributes: ObjectId number(10), BuildingLevelElevation number(31), BuildingLevelRoomOffset number(31), BuildingLevelIsStory string(3), Dimensions.RoomArea number(31), BaseCategory string(5), BuildingLevel string(24), Category string(5), Discipline string(13), ElementType string(8), Family string(2), FamilyType string(2), IdentityData.RoomName string(7), IdentityData.RoomNumber string(2), InExteriorShell string(3), RoomSchedule.Area number(31), UniqueId string(45), WorksetName string(8)
GeometryColorSetter
    ALPHA = 1
    GQUERY:
      for $geom in //geometry
      where $geom/@fme_geometry_name = ''
      or $geom/@fme_geometry_name = ''
      return number($geom/@fme_id)
    MODE = Random
    REC = Yes
    SIDE = Both
Architectural.Walls (reader REVITNATIVE_1)
    attributes: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
SurveyPoint (reader REVITNATIVE_1)
