FME workspace revitnative_revitnative2none.fmw

Parameters:
- SourceDataset_REVITNATIVE =
- SourceDataset_REVITNATIVE_3 =

Readers:
- REVITNATIVE_1: REVITNATIVE from $(SourceDataset_REVITNATIVE)
- REVITNATIVE_2: REVITNATIVE from $(SourceDataset_REVITNATIVE_3)

ChangeDetector
    BLANK_AND_MISSING_NAMES_TRAITS_DIFFER = No
    CHECK_COORDINATE_SYSTEMS = No
    LENIENT_MATCH = No
    MATCH = FULL
    PREEMPTIVE_ATTRS = UniqueId
    UNCHANGED_OUTPUT = Output Original
    UPDATED -> GeometryColorSetter
    INSERTED -> GeometryColorSetter_2
    UNCHANGED -> GeometryColorSetter_3
GeometryColorSetter
    ALPHA = .7
    FILL_COLOR = 0,0,1
    MODE = Fixed
    REC = Yes
    SIDE = Both
GeometryColorSetter_2
    ALPHA = .7
    FILL_COLOR = 0.333333,1,0
    MODE = Fixed
    REC = Yes
    SIDE = Both
GeometryColorSetter_3
    ALPHA = .3
    FILL_COLOR = 0.4,0.4,0.4
    MODE = Fixed
    REC = Yes
    SIDE = Both

Bookmark: OLD
Architectural.CurtainWallMullions (reader REVITNATIVE_1)
    attributes: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
Architectural.Columns (reader REVITNATIVE_1)
    attributes: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
Architectural.CurtainPanels (reader REVITNATIVE_1)
    attributes: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
Architectural.Rooms (reader REVITNATIVE_1)
    attributes: ObjectId number(10,0), BuildingLevelElevation number(31,15), BuildingLevelRoomOffset number(31,15), BuildingLevelIsStory char(3), Dimensions.RoomArea number(31,15), BaseCategory char(5), BuildingLevel char(24), Category char(5), Discipline char(13), ElementType char(8), Family char(0), FamilyType char(0), IdentityData.RoomName char(10), IdentityData.RoomNumber char(1), InExteriorShell char(3), UniqueId char(45), WorksetName char(8)
    -> ChangeDetector [ORIGINAL]
Metadata.FileInformation (reader REVITNATIVE_1)
    attributes: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
Metadata.ViewInformation (reader REVITNATIVE_1)
    attributes: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
Architectural.Doors (reader REVITNATIVE_1)
    attributes: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
Architectural.Floors (reader REVITNATIVE_1)
    attributes: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
Architectural.Lines (reader REVITNATIVE_1)
    attributes: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
Architectural.Walls (reader REVITNATIVE_1)
    attributes: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
SurveyPoint (reader REVITNATIVE_1)

Bookmark: New
Architectural.CurtainWallMullions (reader REVITNATIVE_2)
    attributes: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
Architectural.Columns (reader REVITNATIVE_2)
    attributes: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
Architectural.CurtainPanels (reader REVITNATIVE_2)
    attributes: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
Architectural.Doors (reader REVITNATIVE_2)
    attributes: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
Architectural.Floors (reader REVITNATIVE_2)
    attributes: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
Architectural.Lines (reader REVITNATIVE_2)
    attributes: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
Architectural.Rooms (reader REVITNATIVE_2)
    attributes: ObjectId number(10,0), BuildingLevelElevation number(31,15), BuildingLevelRoomOffset number(31,15), BuildingLevelIsStory char(3), Dimensions.RoomArea number(31,15), BaseCategory char(5), BuildingLevel char(24), Category char(5), Discipline char(13), ElementType char(8), Family char(0), FamilyType char(0), IdentityData.RoomName char(10), IdentityData.RoomNumber char(1), InExteriorShell char(3), UniqueId char(45), WorksetName char(8)
    -> ChangeDetector [REVISED]
Architectural.Walls (reader REVITNATIVE_2)
    attributes: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
Metadata.FileInformation (reader REVITNATIVE_2)
    attributes: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
Metadata.ViewInformation (reader REVITNATIVE_2)
    attributes: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
SurveyPoint (reader REVITNATIVE_2)
