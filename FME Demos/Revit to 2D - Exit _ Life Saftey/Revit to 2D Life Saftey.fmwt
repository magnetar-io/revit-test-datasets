FME workspace Revit to 2D Life Saftey.fmwt
Title: Revit to 2D Fire Rating

Parameters:
- FEATURE_TYPES =
- SourceDataset_REVITNATIVE =

Readers:
- REVITNATIVE_1: REVITNATIVE from $(SourceDataset_REVITNATIVE)

Metadata.FileInformation (reader REVITNATIVE_1)
    attributes: DocVer char(18), DocUpdate char(14), AuthorUsername char(0), CreatedBy char(14), CentralModelPath char(0), IsCentralModel boolean, IsCreatedLocally boolean, ProjectUnit char(5), LevelElevationInfo.Level 1 number(31,15), LevelElevationInfo.Basement 1 number(31,15), LevelElevationInfo.Basement 2 number(31,15), LevelElevationInfo.Mez 1-2 number(31,15), LevelElevationInfo.Level 4 - Wall Layouts 3 number(31,15), LevelElevationInfo.Level 3 - Wall Layouts 1 number(31,15), LevelElevationInfo.Level 4 - Wall Layouts 2 number(31,15), AnalyticalProperties.AnalyticConstruction char(6), AnalyticalProperties.DefineThermalPropertiesby number(10,0), BaseCategory char(5), BuildingLevel char(24), BuildingLevelElevation number(31,15), BuildingLevelIsStory char(3), BuildingLevelRoomOffset number(31,15), Category char(5), Constraints.BaseExtensionDistance number(31,15), Constraints.BaseOffset number(31,15), Constraints.HeightOffsetFromLevel number(31,15), Constraints.Offset number(31,15), Constraints.TopExtensionDistance number(31,15), Constraints.TopOffset number(31,15), Constraints.UnconnectedHeight number(31,15),
      Construction.Function number(10,0), Construction.Thickness number(31,15), Construction.WallClosure number(10,0), CreatedPhase char(16), DetailLevel char(6), Dimensions.Depth number(31,15), Dimensions.Height number(31,15), Dimensions.RoomArea number(31,15), Dimensions.Thickness number(31,15), Dimensions.TrimProjectionExt number(31,15), Dimensions.TrimProjectionInt number(31,15), Dimensions.TrimWidth number(31,15), Dimensions.Width number(31,15), Dimensions.Widthonside1 number(31,15), Dimensions.Widthonside2 number(31,15), Discipline char(13), ElementType char(8), Elevation number(31,15), Family char(0), FamilyType char(0), Function char(8), Graphics.CoarseScaleFillColor number(10,0), HostFeatureType char(19), HostId number(10,0), IdentityData.FireRating char(0), IdentityData.OmniclassNumber char(17), IdentityData.OmniclassTitle char(7), IdentityData.RoomName char(7), IdentityData.RoomNumber char(2), IdentityData.TypeMark char(1),
      InExteriorShell char(3), IsTemplateView boolean, MaterialsandFinishes.DoorMaterial char(12), MaterialsandFinishes.FrameMaterial char(12), Name char(28), ObjectId number(10,0), Orientation char(13), Other.WALL_BASE_OFFSET_COMPUTED number(31,15), Other.WALL_FAKE_END_PARAM_0 number(31,15), Other.WALL_FAKE_END_PARAM_1 number(31,15), Other.WALL_HEIGHT_PARAM number(31,15), RoomSchedule.Area number(31,15), Scale char(6), Structural.SpanDirection number(31,15), Structural.Structural boolean, Template char(4), Type char(15), UniqueId char(45), ViewDepth.Level char(24), ViewDepth.Offset number(31,15), ViewRangeBottom.Level char(24), ViewRangeBottom.Offset number(31,15), ViewRangeCutPlane.Level char(24), ViewRangeCutPlane.Offset number(31,15), ViewRangeTop.Level char(24), ViewRangeTop.Offset number(31,15), WorksetName char(8)
    -> FeatureTypeFilter
FeatureTypeFilter
    ATTRIBUTES = <Blank>,<Unfiltered>,Architectural.Grids,Architectural.Views,Architectural.Lines,Architectural.RoomReference,Architectural.Floors
    <UNFILTERED> -> AttributeManager
AttributeManager
    ATTR_TABLE = SET_TO Fire Rating = FME_CONDITIONAL:DEFAULT_VALUE'_FME_NO_OP_'BOOL_OP;OR;COMPOSITE_TEST;1;CASE_INSENSITIVE_TEST @Value(FamilyType) CONTAINS 1 Hour'1HR'BOOL_OP;OR;COMPOSITE_TEST;1;CASE_INSENSITIVE_TEST @Value(FamilyType) CONTAINS 2 Hour'2HR'BOOL_OP;OR;COMPOSITE_TEST;1;CASE_INSENSITIVE_TEST @Value(FamilyType) CONTAINS 3 Hour'3HR'FME_NUM_CONDITIONS4___
    -> AttributeFilter
AttributeFilter
    ATTR_NAME = Fire Rating
    ATTR_VALUES = <Empty>,<Missing>,<Null>,<Unfiltered>,1HR,2HR,3HR
    <MISSING> -> FeatureColorSetter_3
    2HR -> FeatureColorSetter
    3HR -> FeatureColorSetter_2
FeatureColorSetter_3
    COLOR = 1,1,1
    FILL_COLOR = 1,1,1
    MODE = Fixed
FeatureColorSetter
    COLOR = 1,0.333333,1
    FILL_COLOR = 1,0.333333,1
    MODE = Fixed
FeatureColorSetter_2
    COLOR = 1,0,0
    FILL_COLOR = 1,0,0
    MODE = Fixed
